package MixedFleet {
    private import ScalarValues::*;
    private import StructuralElements::*;
    private import RequirementsSpace::*;
    private import ActionsSpace::*;
    private import Verefication::*;
    private import VerificationCases::*;
    private import SI::*;
    
    action  Mission{

        attribute defaultLocation :Number= 3;
        attribute defaultLocationObject : Coordinate{
            :>> X = 50.0 ;
            :>> Y = 50.0 ;
            :>> Z = 50.0 ;
        }; 

        part forklift_1 : Forklift {
            attribute :>> id = "FORK-001";
            attribute :>> autonomyLevel = 1;
            attribute :>> liftingCapacity = 5000.0 [kg];
            attribute :>> forkHeight = 6.0 [m] ;
            
            perform pick_up ;
            perform move ;
            perform drop;
            
        }
        
        part drone_1 : Uav {
            attribute :>> id = "DRONE-001";
            attribute :>> autonomyLevel = 2.0;
            attribute :>> scanRange = 1000.0[m];

            perform search;
        }

        action search{  
            out empty_location;
            out status;
        }

        action pick_up{
            in object = "euro_pallet_1";
            out status;
        }


        action move{
            in destination = search.empty_location;
            out status;
        }

        action drop {
            in object = "euro_pallet_1";
            out status;
        }

        first start;
        then 
            perform search;
        if(defaultLocation == 3){ 
            perform pick_up;
        }else{
            perform search;
        }
        then
            perform move;
        then
            perform drop;   
        then done;             

    }
}
